SPNEGOASNOneSpec {
    iso(1) identified-organization(3) dod(6) internet(1)
    security(5) mechanism(5) snego (2) modules(4) spec2(2)
} DEFINITIONS EXPLICIT TAGS ::= BEGIN

MechType ::= OBJECT IDENTIFIER
    -- OID represents each security mechanism as suggested by
    -- [RFC2743]

MechTypeList ::= SEQUENCE OF MechType

NegotiationToken ::= CHOICE {
    negTokenInit    [0] NegTokenInit,
    negTokenResp    [1] NegTokenResp
}

NegTokenInit ::= SEQUENCE {
    mechTypes       [0] MechTypeList,
    reqFlags        [1] ContextFlags  OPTIONAL,
        -- inherited from RFC 2478 for backward compatibility,
        -- RECOMMENDED to be left out
    mechToken       [2] OCTET STRING  OPTIONAL,
    mechListMIC     [3] OCTET STRING  OPTIONAL,
    ...
}
NegTokenResp ::= SEQUENCE {
    negState       [0] ENUMERATED {
        accept-completed    (0),
        accept-incomplete   (1),
        reject              (2),
        request-mic         (3)
    }                                 OPTIONAL,
        -- REQUIRED in the first reply from the target
    supportedMech   [1] MechType      OPTIONAL,
        -- present only in the first reply from the target
    responseToken   [2] OCTET STRING  OPTIONAL,
    mechListMIC     [3] OCTET STRING  OPTIONAL,
    ...
}

ContextFlags ::= BIT STRING {
    delegFlag       (0),
    mutualFlag      (1),
    replayFlag      (2),
    sequenceFlag    (3),
    anonFlag        (4),
    confFlag        (5),
    integFlag       (6)
} (SIZE (32))

NegHints ::= SEQUENCE {
        hintName[0] GeneralString OPTIONAL,
        hintAddress[1] OCTET STRING OPTIONAL
}
NegTokenInit2 ::= SEQUENCE {
        mechTypes[0] MechTypeList OPTIONAL,
        reqFlags [1] ContextFlags OPTIONAL,
        mechToken [2] OCTET STRING OPTIONAL,
        negHints [3] NegHints OPTIONAL,
        mechListMIC [4] OCTET STRING OPTIONAL,
        ...
}

END

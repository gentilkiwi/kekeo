CredSSP DEFINITIONS ::= BEGIN

TSRequest ::= SEQUENCE {
	version     [0] INTEGER,
	negoTokens  [1] NegoData OPTIONAL,
	authInfo    [2] OCTET STRING OPTIONAL,
	pubKeyAuth  [3] OCTET STRING OPTIONAL,
	errorCode   [4] INTEGER OPTIONAL,
	clientNonce [5] OCTET STRING OPTIONAL
}

NegoData ::= SEQUENCE OF SEQUENCE {
	negoToken	[0] OCTET STRING
}

TSCredentials ::= SEQUENCE {
	credType	[0] INTEGER,
	credentials	[1] OCTET STRING
}

TSPasswordCreds ::= SEQUENCE {
	domainName  [0] OCTET STRING,
	userName    [1] OCTET STRING,
	password    [2] OCTET STRING
}

TSSmartCardCreds ::= SEQUENCE {
	pin         [0] OCTET STRING,
	cspData     [1] TSCspDataDetail,
	userHint    [2] OCTET STRING OPTIONAL,
	domainHint  [3] OCTET STRING OPTIONAL
}

TSCspDataDetail ::= SEQUENCE {
	keySpec       [0] INTEGER,
	cardName      [1] OCTET STRING OPTIONAL,
	readerName    [2] OCTET STRING OPTIONAL,
	containerName [3] OCTET STRING OPTIONAL,
	cspName       [4] OCTET STRING OPTIONAL
}

TSRemoteGuardCreds ::= SEQUENCE{
	logonCred           [0] TSRemoteGuardPackageCred,
	supplementalCreds   [1] SEQUENCE OF TSRemoteGuardPackageCred OPTIONAL
}

TSRemoteGuardPackageCred ::= SEQUENCE{
	packageName [0] OCTET STRING,
	credBuffer  [1] OCTET STRING
}
END
